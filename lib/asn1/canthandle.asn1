-- $Id$ --

CANTHANDLE DEFINITIONS ::= BEGIN

--  Can't handle primitives in SET OF, causing the compiler to crash
--  Workaround is to define a type that is only an integer and use that

Baz ::= SET OF INTEGER

END
